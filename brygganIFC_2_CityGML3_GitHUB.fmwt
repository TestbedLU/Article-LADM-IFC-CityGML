FME workspace brygganIFC_2_CityGML3_GitHUB.fmwt
Title: brygganIFC_2_CityGML3_GitHUB

Parameters:
- koordinatsystemPlanIdentifier = urn:ogc:def:crs:EPSG::3008   # Välj identifier för koordinatsystem i plan
- coordSysPlane = http://www.opengis.net/def/crs/EPSG/0/3008   # " " Coordinate system in plane
- DestDataset_TEXTLINE = $(FME_MF_DIR)CityGML3\BrygganCityModelCityGML3_Groups.gml   # Destination Text File
- SourceDataset_XML = $(FME_MF_DIR)cityModelandMultihuset/multihuset_LOD2_surfaces.gml   # Source XML File(s)
- SourceDataset_FFS = $(FME_MF_DIR)IfcSpacesONLY.ffs   # Source FME Feature Store (FFS) File(s)

Readers:
- XML_1: XML from $(SourceDataset_XML)
- FFS_2: FFS from $(SourceDataset_FFS)

Writers:
- TEXTLINE_1: TEXTLINE to $(DestDataset_TEXTLINE)

Note: Workspace to convert legal spaces in an IFC-file to a CityGML3-file with logical spaces (BuildingUnit elements) / The legal spaces (IfcSpace elements) are converted to GML and XMLTemplater transformers are used to build the CityGML3-file. / Note that the schema files (xsd) needs to be downloaded from: https://github.com/opengeospatial/CityGML-3.0Encodings / and saved on C:\xsd\ (It can be handled in a different manner but the script needs to access the schemas)
Note: This workspace is released under the 3-Clause BSD License. For details, see https://opensource.org/licenses/BSD-3-Clause / This work was supported by the research platform, Smart Built Environment program under Grant 2016-01981 (financed by Formas, Vinnova and Swedish Energy Agency) and Lund University. / Copyright (c) 2019, Lunds universitet / All rights reserved.
Note: Adding attribute for cadastre name (hard-coded Bryggan 1 and Bryggan 2)
PythonCaller_attributeAdder_2
    NEW_ATTRIBUTES = cadastreName
    PYTHONSOURCE:
      import fme
      import fmeobjects
      import xlsxwriter

      # #################################################################
      # FeatureProcessor
      # #################################################################
      class FeatureProcessor(object):
          def __init__(self):
              self.space = []

          def input(self,feature):
              self.space.append(feature)

          def close(self):

              for sp in self.space:

                  if 'Bryggan1' in sp.getAttribute('LongName'):
                      sp.setAttribute('cadastreName', 'Bryggan 1')
                  elif 'Bryggan2' in sp.getAttribute('LongName'):
                      sp.setAttribute('cadastreName', 'Bryggan 2')


                  self.pyoutput(sp)
    PYTHONSYMBOL = FeatureProcessor
    -> AttributeKeeper
AttributeKeeper
    KEEP_ATTRS = Name,cadastreName,GlobalId
    -> AttributeCreator
AttributeCreator
    ATTR_TABLE:
      SET_TO lod = lod1Solid
      SET_TO coordSysPlane = $(coordSysPlane)
      SET_TO SpaceID = Space_@Value(Name)
    -> GeometryExtractor
    -> AttributeCreator_4
Note: To get CityGML geometries.
GeometryExtractor
    ATTR = _geometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> TestFilter_2
AppearanceSetter_Output: Inspector
AppearanceSetter_2_Output: Inspector
Creator
    GEOMTYPE = Geometry Object
    NUM = 1
    CREATED -> UUIDGenerator_CityModelID
UUIDGenerator_CityModelID
    UUID_ATTR = _CM_gml_id
    -> XMLTemplater_5 [ROOT]

Bookmark: Reading IFC-file with the legal spaces
  The original IFC-cannot be published so here an FME FFS-file with the spaces only is imported.
Space (reader FFS_2)
    attributes: element_parent_id varchar(200), element_id varchar(200), Name varchar(200), GlobalId varchar(200), LongName varchar(200), InteriorOrExteriorSpace varchar(200), BaseQuantities.GrossFloorArea real64, BaseQuantities.GrossPerimeter real64, BaseQuantities.GrossVolume real64, BaseQuantities.Height real64, BaseQuantities.NetFloorArea real64, Constraints.Base Offset real64, Constraints.Level varchar(200), Constraints.Limit Offset real64, Constraints.Upper Limit varchar(200), Dimensions.Area real64, Dimensions.Computation Height real64, Dimensions.Perimeter real64, Dimensions.Unbounded Height real64, Phasing.Phase (utf-8) varchar(200), Pset_SpaceCommon.Reference (utf-8) varchar(200)
    -> PythonCaller_attributeAdder_2

Bookmark: Handling CityObjectGroups
  Note that cadaster unit names (Bryggan 1 and Bryggan 2) are hard coded.
AttributeCreator_4
    ATTR_TABLE:
      SET_TO tagSpaceID = <grp:groupMember xlink:href="#@Value(SpaceID)"/>
      SET_TO cadastreGMLID = grp_@Value(cadastreName)
    -> Aggregator_2
Aggregator_2
    ACCUM_ATTRS_NAME = Drop Incoming Attributes
    GROUP_BY = cadastreGMLID
    LIST_ATTRS_TO_INCLUDE = tagSpaceID
    LIST_NAME = SpaceIDList
    MODE = Attributes Only
    ORDERED = No
    SEP = ,
    AGGREGATE -> XMLTemplater_8 [ROOT]
Note: Adding CityObjectGroups and spaces belonging to the groups.
XMLTemplater_8
    CONSECUTIVE_GROUPS = No
    GROUP_BY = cadastreGMLID
    OUTPUT_XML_HEADER = No
    RESULT_ATTRIBUTE = _CadastreUnitGroups
    ROOT_QUERY_EXPR:
      	<core:cityObjectMember xmlns:grp="http://www.opengis.net/citygml/cityobjectgroup/3.0" xmlns:app="http://www.opengis.net/citygml/appearance/3.0" xmlns:bldg="http://www.opengis.net/citygml/building/3.0" xmlns:brid="http://www.opengis.net/citygml/bridge/3.0" xmlns:con="http://www.opengis.net/citygml/construction/3.0" xmlns:core="http://www.opengis.net/citygml/3.0" xmlns:dyn="http://www.opengis.net/citygml/dynamizer/3.0" xmlns:fes="http://www.opengis.net/fes/2.0" xmlns:gco="http://www.isotc211.org/2005/gco" xmlns:gen="http://www.opengis.net/citygml/generics/3.0" xmlns:gmd="http://www.isotc211.org/2005/gmd" xmlns:gml="http://www.opengis.net/gml/3.2" xmlns:gmlcov="http://www.opengis.net/gmlcov/1.0" xmlns:gsr="http://www.isotc211.org/2005/gsr" xmlns:gss="http://www.isotc211.org/2005/gss" xmlns:gts="http://www.isotc211.org/2005/gts" xmlns:om="http://www.opengis.net/om/2.0" xmlns:ows="http://www.opengis.net/ows/1.1" xmlns:p="urn:oasis:names:tc:ciq:xsdschema:xAL:2.0" xmlns:sam="http://www.opengis.net/sampling/2.0" xmlns:sams="http://www.opengis.net/samplingSpatial/2.0" xmlns:sos="http://www.opengis.net/sos/2.0" xmlns:swe="http://www.opengis.net/swe/2.0" xmlns:swes="http://www.opengis.net/swes/2.0" xmlns:tns="http://www.w3.org/2005/08/addressing" xmlns:tsml="http://www.opengis.net/tsml/1.0" xmlns:tun="http://www.opengis.net/citygml/tunnel/3.0" xmlns:vers="http://www.opengis.net/citygml/versioning/3.0" xmlns:wstop="http://docs.oasis-open.org/wsn/t-1" xmlns:xlink="http://www.w3.org/1999/xlink" xmlns:xml="http://www.w3.org/XML/1998/namespace" xmlns:xsi="http://www.w3.org/2001/XMLSchema-instance" xsi:schemaLocation="http://www.opengis.net/citygml/3.0 file:\C:\xsd\CityGML-3\core\cityGMLBase.xsd http://www.opengis.net/citygml/building/3.0 file:\C:\xsd\CityGML-3\bldg\building.xsd http://www.opengis.net/citygml/cityobjectgroup.xsd/3.0 file:\C:\xsd\CityGML-3\grp\cityobjectgroup.xsd">
              <grp:CityObjectGroup gml:id="{fme:get-attribute("cadastreGMLID")}">
                  {for $v in fme:get-list-attribute("SpaceIDList{}.tagSpaceID")
                  return $v}
              </grp:CityObjectGroup>
          </core:cityObjectMember>
    VISIBLE_QUERY_VALIDATE = Yes
    -> StringReplacer_10
Note: Replacing "&lt;" with "<".
StringReplacer_10
    CASE = NO
    FIND_TEXT = &lt;
    NO_MATCH = _FME_NO_OP_
    REGEXP = NO
    REPLACE_TEXT = <
    SRC_ATTRS = _CadastreUnitGroups
    -> StringReplacer_11
Note: Replacing "&gt;" with ">"
StringReplacer_11
    CASE = NO
    FIND_TEXT = &gt;
    NO_MATCH = _FME_NO_OP_
    REGEXP = NO
    REPLACE_TEXT = >
    SRC_ATTRS = _CadastreUnitGroups
    -> XMLFormatter
Note: To get each space on individual lines.
XMLFormatter
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = No
    REPLACE_TABS_WITH_SPACES = no
    SCHEMALOC_CLEANUP = No
    TEXT_INDENT = no
    WHITESPACE_HANDLING = Preserve all whitespace
    XML_ATTR_TEXT = _CadastreUnitGroups
    XML_INPUT_TYPE = Attribute Specifying XML Text
    XML_OUTPUT_ATTR = _xml_output
    XML_OUTPUT_TYPE = Attribute
    PASSED -> XMLTemplater_5 [CITYOBJECTGROUP]

Bookmark: Only to add appearance to visualisation
TestFilter_2
    DEFAULT_VALUE = <UNFILTERED>
    TEST_LIST = "BOOL_OP,OR,COMPOSITE_TEST,""""""<Unused>"""""",TEST_CLAUSE,TEST @Value(cadastreName) = Bryggan 1",Bryggan1,"BOOL_OP,OR,COMPOSITE_TEST,""""""<Unused>"""""",TEST_CLAUSE,TEST @Value(cadastreName) = Bryggan 2",Bryggan2
    Bryggan1 -> AppearanceSetter [GEOMETRY]
    Bryggan2 -> AppearanceSetter_2 [GEOMETRY]
AppearanceSetter
    AMBIENT_COLOR = 0.666667,0,0
    DEF_STORAGE = Create New Definitions
    DIFFUSE_COLOR = 0.666667,0,0
    EMISSIVE_COLOR = 0.666667,0,0
    GQUERY:
      for $geom in //geometry
      where $geom/count(parent::geometry) = 0
      return number($geom/@fme_id)
    SET_ON_SIDE = Front and Back Sides
    SPECULAR_COLOR = 0.666667,0,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> AppearanceSetter_Output
    -> XMLTemplater_7 [BUILDINGUNITS]
AppearanceSetter_2
    AMBIENT_COLOR = 0,0.666667,0
    DEF_STORAGE = Create New Definitions
    DIFFUSE_COLOR = 0,0.666667,0
    EMISSIVE_COLOR = 0,0.666667,0
    GQUERY:
      for $geom in //geometry
      where $geom/count(parent::geometry) = 0
      return number($geom/@fme_id)
    SET_ON_SIDE = Front and Back Sides
    SPECULAR_COLOR = 0,0.666667,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> AppearanceSetter_2_Output
    -> XMLTemplater_7 [BUILDINGUNITS]

Bookmark: Reading Global ID of the building
  Original versions read the IFC buidling but the IFC-file cannot be published so here a creator is used.
Creator_Building
    GEOMTYPE = Geometry Object
    NUM = 1
    CREATED -> AttributeCreator_2
AttributeCreator_2
    ATTR_TABLE = SET_TO GlobalId = fakeID
    -> XMLTemplater_7 [ROOT]

Bookmark: Genererar GML-fil (bounded by not included)
Note: Creates XML-code for the legal spaces (BuildingUnits)
XMLTemplater_7
    BUILDINGUNITS_QUERY_EXPR:
      			<bldg:BuildingUnit gml:id="{fme:get-attribute('SpaceID')}"  xmlns:app="http://www.opengis.net/citygml/appearance/3.0" xmlns:bldg="http://www.opengis.net/citygml/building/3.0" xmlns:brid="http://www.opengis.net/citygml/bridge/3.0" xmlns:con="http://www.opengis.net/citygml/construction/3.0" xmlns:core="http://www.opengis.net/citygml/3.0" xmlns:dyn="http://www.opengis.net/citygml/dynamizer/3.0" xmlns:fes="http://www.opengis.net/fes/2.0" xmlns:gco="http://www.isotc211.org/2005/gco" xmlns:gen="http://www.opengis.net/citygml/generics/3.0" xmlns:gmd="http://www.isotc211.org/2005/gmd" xmlns:gml="http://www.opengis.net/gml/3.2" xmlns:gmlcov="http://www.opengis.net/gmlcov/1.0" xmlns:gsr="http://www.isotc211.org/2005/gsr" xmlns:gss="http://www.isotc211.org/2005/gss" xmlns:gts="http://www.isotc211.org/2005/gts" xmlns:om="http://www.opengis.net/om/2.0" xmlns:ows="http://www.opengis.net/ows/1.1" xmlns:p="urn:oasis:names:tc:ciq:xsdschema:xAL:2.0" xmlns:sam="http://www.opengis.net/sampling/2.0" xmlns:sams="http://www.opengis.net/samplingSpatial/2.0" xmlns:sos="http://www.opengis.net/sos/2.0" xmlns:swe="http://www.opengis.net/swe/2.0" xmlns:swes="http://www.opengis.net/swes/2.0" xmlns:tns="http://www.w3.org/2005/08/addressing" xmlns:tsml="http://www.opengis.net/tsml/1.0" xmlns:tun="http://www.opengis.net/citygml/tunnel/3.0" xmlns:vers="http://www.opengis.net/citygml/versioning/3.0" xmlns:wstop="http://docs.oasis-open.org/wsn/t-1" xmlns:xlink="http://www.w3.org/1999/xlink" xmlns:xml="http://www.w3.org/XML/1998/namespace" xmlns:xsi="http://www.w3.org/2001/XMLSchema-instance" xsi:schemaLocation="http://www.opengis.net/citygml/3.0 file:\C:\xsd\CityGML-3\core\cityGMLBase.xsd http://www.opengis.net/citygml/building/3.0 file:\C:\xsd\CityGML-3\bldg\building.xsd">
      				<core:spaceType>closed</core:spaceType>
                      <bldg:class>{fme:get-attribute("cadastreName")}</bldg:class>
                      <core:genericAttribute>
                          <gen:StringAttribute>
                              <gen:name>Cadastre unit</gen:name>
                              <gen:value>{fme:get-attribute("cadastreName")}</gen:value>
                          </gen:StringAttribute>
                          <gen:StringAttribute>
                              <gen:name>Logical space ID</gen:name>
                              <gen:value>{fme:get-attribute("SpaceID")}</gen:value>
                          </gen:StringAttribute>
                      </core:genericAttribute>
      				<core:lod1Solid>
      					{fme:get-attribute("_geometry")}
      				</core:lod1Solid>
      			</bldg:BuildingUnit>
    OUTPUT_XML_HEADER = No
    RESULT_ATTRIBUTE = _BuildingUnits
    ROOT_QUERY_EXPR:
      	<core:cityObjectMember  xmlns:app="http://www.opengis.net/citygml/appearance/3.0" xmlns:bldg="http://www.opengis.net/citygml/building/3.0" xmlns:brid="http://www.opengis.net/citygml/bridge/3.0" xmlns:con="http://www.opengis.net/citygml/construction/3.0" xmlns:core="http://www.opengis.net/citygml/3.0" xmlns:dyn="http://www.opengis.net/citygml/dynamizer/3.0" xmlns:fes="http://www.opengis.net/fes/2.0" xmlns:gco="http://www.isotc211.org/2005/gco" xmlns:gen="http://www.opengis.net/citygml/generics/3.0" xmlns:gmd="http://www.isotc211.org/2005/gmd" xmlns:gml="http://www.opengis.net/gml/3.2" xmlns:gmlcov="http://www.opengis.net/gmlcov/1.0" xmlns:gsr="http://www.isotc211.org/2005/gsr" xmlns:gss="http://www.isotc211.org/2005/gss" xmlns:gts="http://www.isotc211.org/2005/gts" xmlns:om="http://www.opengis.net/om/2.0" xmlns:ows="http://www.opengis.net/ows/1.1" xmlns:p="urn:oasis:names:tc:ciq:xsdschema:xAL:2.0" xmlns:sam="http://www.opengis.net/sampling/2.0" xmlns:sams="http://www.opengis.net/samplingSpatial/2.0" xmlns:sos="http://www.opengis.net/sos/2.0" xmlns:swe="http://www.opengis.net/swe/2.0" xmlns:swes="http://www.opengis.net/swes/2.0" xmlns:tns="http://www.w3.org/2005/08/addressing" xmlns:tsml="http://www.opengis.net/tsml/1.0" xmlns:tun="http://www.opengis.net/citygml/tunnel/3.0" xmlns:vers="http://www.opengis.net/citygml/versioning/3.0" xmlns:wstop="http://docs.oasis-open.org/wsn/t-1" xmlns:xlink="http://www.w3.org/1999/xlink" xmlns:xml="http://www.w3.org/XML/1998/namespace" xmlns:xsi="http://www.w3.org/2001/XMLSchema-instance" xsi:schemaLocation="http://www.opengis.net/citygml/3.0 file:\C:\xsd\CityGML-3\core\cityGMLBase.xsd http://www.opengis.net/citygml/building/3.0 file:\C:\xsd\CityGML-3\bldg\building.xsd">
              <bldg:Building gml:id="{fme:get-attribute("GlobalId")}">
                  <gml:description>3D cadastre of one floor of the multihuset building</gml:description>
                  <gml:name>Multihuset, Bryggan 1 and Bryggan 2</gml:name>
                  <bldg:buildingSubdivision>
                  {fme:process-features("BUILDINGUNITS")}
                  </bldg:buildingSubdivision>
      		</bldg:Building>
          </core:cityObjectMember>
    VISIBLE_QUERY_VALIDATE = Yes
    -> StringReplacer_6
Note: Replacing "&lt;" with "<"
StringReplacer_6
    CASE = NO
    FIND_TEXT = &lt;
    NO_MATCH = _FME_NO_OP_
    REGEXP = NO
    REPLACE_TEXT = <
    SRC_ATTRS = _BuildingUnits
    -> StringReplacer_7
Note: Replacing "&gt;" with ">"
StringReplacer_7
    CASE = NO
    FIND_TEXT = &gt;
    NO_MATCH = _FME_NO_OP_
    REGEXP = NO
    REPLACE_TEXT = >
    SRC_ATTRS = _BuildingUnits
    -> XMLTemplater_5 [BUILDINGUNITS]
Note: Creates XML-code for the (new) building model and the entire city model.
XMLTemplater_5
    BUILDINGUNITS_QUERY_EXPR = {fme:get-attribute("_BuildingUnits")}
    CITYOBJECTGROUP_QUERY_EXPR = {fme:get-attribute("_CadastreUnitGroups")}
    OTHERBUILDINGS_QUERY_EXPR:
      	<core:cityObjectMember xmlns:app="http://www.opengis.net/citygml/appearance/3.0" xmlns:bldg="http://www.opengis.net/citygml/building/3.0" xmlns:brid="http://www.opengis.net/citygml/bridge/3.0" xmlns:con="http://www.opengis.net/citygml/construction/3.0" xmlns:core="http://www.opengis.net/citygml/3.0" xmlns:dyn="http://www.opengis.net/citygml/dynamizer/3.0" xmlns:fes="http://www.opengis.net/fes/2.0" xmlns:gco="http://www.isotc211.org/2005/gco" xmlns:gen="http://www.opengis.net/citygml/generics/3.0" xmlns:gmd="http://www.isotc211.org/2005/gmd" xmlns:gml="http://www.opengis.net/gml/3.2" xmlns:gmlcov="http://www.opengis.net/gmlcov/1.0" xmlns:gsr="http://www.isotc211.org/2005/gsr" xmlns:gss="http://www.isotc211.org/2005/gss" xmlns:gts="http://www.isotc211.org/2005/gts" xmlns:om="http://www.opengis.net/om/2.0" xmlns:ows="http://www.opengis.net/ows/1.1" xmlns:p="urn:oasis:names:tc:ciq:xsdschema:xAL:2.0" xmlns:sam="http://www.opengis.net/sampling/2.0" xmlns:sams="http://www.opengis.net/samplingSpatial/2.0" xmlns:sos="http://www.opengis.net/sos/2.0" xmlns:swe="http://www.opengis.net/swe/2.0" xmlns:swes="http://www.opengis.net/swes/2.0" xmlns:tns="http://www.w3.org/2005/08/addressing" xmlns:tsml="http://www.opengis.net/tsml/1.0" xmlns:tun="http://www.opengis.net/citygml/tunnel/3.0" xmlns:vers="http://www.opengis.net/citygml/versioning/3.0" xmlns:wstop="http://docs.oasis-open.org/wsn/t-1" xmlns:xlink="http://www.w3.org/1999/xlink" xmlns:xml="http://www.w3.org/XML/1998/namespace" xmlns:xsi="http://www.w3.org/2001/XMLSchema-instance" xsi:schemaLocation="http://www.opengis.net/citygml/3.0 file:\C:\xsd\CityGML-3\core\cityGMLBase.xsd http://www.opengis.net/citygml/building/3.0 file:\C:\xsd\CityGML-3\bldg\building.xsd">
              <bldg:Building gml:id="{fme:get-attribute('_gml_id_BD')}">
                  <core:spaceType>semiOpen</core:spaceType>
                  <core:lod2MultiSurface>
                      {fme:get-attribute("_geometry")}
                  </core:lod2MultiSurface>
              </bldg:Building>
          </core:cityObjectMember>
    OUTPUT_XML_HEADER = No
    RESULT_ATTRIBUTE = _result
    ROOT_QUERY_EXPR:
      <?xml version="1.0" encoding="UTF-8"?>
      <core:CityModel xmlns:grp="http://www.opengis.net/citygml/cityobjectgroup/3.0" xmlns:app="http://www.opengis.net/citygml/appearance/3.0" xmlns:bldg="http://www.opengis.net/citygml/building/3.0" xmlns:brid="http://www.opengis.net/citygml/bridge/3.0" xmlns:con="http://www.opengis.net/citygml/construction/3.0" xmlns:core="http://www.opengis.net/citygml/3.0" xmlns:dyn="http://www.opengis.net/citygml/dynamizer/3.0" xmlns:fes="http://www.opengis.net/fes/2.0" xmlns:gco="http://www.isotc211.org/2005/gco" xmlns:gen="http://www.opengis.net/citygml/generics/3.0" xmlns:gmd="http://www.isotc211.org/2005/gmd" xmlns:gml="http://www.opengis.net/gml/3.2" xmlns:gmlcov="http://www.opengis.net/gmlcov/1.0" xmlns:gsr="http://www.isotc211.org/2005/gsr" xmlns:gss="http://www.isotc211.org/2005/gss" xmlns:gts="http://www.isotc211.org/2005/gts" xmlns:om="http://www.opengis.net/om/2.0" xmlns:ows="http://www.opengis.net/ows/1.1" xmlns:p="urn:oasis:names:tc:ciq:xsdschema:xAL:2.0" xmlns:sam="http://www.opengis.net/sampling/2.0" xmlns:sams="http://www.opengis.net/samplingSpatial/2.0" xmlns:sos="http://www.opengis.net/sos/2.0" xmlns:swe="http://www.opengis.net/swe/2.0" xmlns:swes="http://www.opengis.net/swes/2.0" xmlns:tns="http://www.w3.org/2005/08/addressing" xmlns:tsml="http://www.opengis.net/tsml/1.0" xmlns:tun="http://www.opengis.net/citygml/tunnel/3.0" xmlns:vers="http://www.opengis.net/citygml/versioning/3.0" xmlns:wstop="http://docs.oasis-open.org/wsn/t-1" xmlns:xlink="http://www.w3.org/1999/xlink" xmlns:xml="http://www.w3.org/XML/1998/namespace" xmlns:xsi="http://www.w3.org/2001/XMLSchema-instance" xsi:schemaLocation="http://www.opengis.net/citygml/3.0 file:\C:\xsd\CityGML-3\core\cityGMLBase.xsd http://www.opengis.net/citygml/building/3.0 file:\C:\xsd\CityGML-3\bldg\building.xsd http://www.opengis.net/citygml/cityobjectgroup.xsd/3.0 file:\C:\xsd\CityGML-3\grp\cityobjectgroup.xsd">
          {fme:process-features("BUILDINGUNITS")}
          {fme:process-features("OTHERBUILDINGS")}
          {fme:process-features("CITYOBJECTGROUP")}
      </core:CityModel>
    VISIBLE_QUERY_VALIDATE = Yes
    -> StringReplacer_8
Note: Replacing "&lt;" with "<".
StringReplacer_8
    CASE = NO
    FIND_TEXT = &lt;
    NO_MATCH = _FME_NO_OP_
    REGEXP = NO
    REPLACE_TEXT = <
    SRC_ATTRS = _result
    -> StringReplacer_9
Note: Replacing "&gt;" with ">"
StringReplacer_9
    CASE = NO
    FIND_TEXT = &gt;
    NO_MATCH = _FME_NO_OP_
    REGEXP = NO
    REPLACE_TEXT = >
    SRC_ATTRS = _result
    -> XMLFormatter_4
XMLFormatter_4
    COLLAPSE_EMPTY_ELEMENT = No
    FORMATTING_CHOICE = Pretty-Print XML
    INDENT_SIZE = 1
    LIST_NAME = _xml_error
    NAMESPACE_CLEANUP = Yes
    OUTPUT_ENCODING = utf-8
    REMOVE_ALL_COMMENT = No
    REMOVE_EMPTY_ELEMENT = Yes
    REPLACE_TABS_WITH_SPACES = no
    SCHEMALOC_CLEANUP = No
    TEXT_INDENT = no
    WHITESPACE_HANDLING = Remove excess whitespace
    XML_ATTR_TEXT = _result
    XML_INPUT_TYPE = Attribute Specifying XML Text
    XML_OUTPUT_ATTR = text_line_data
    XML_OUTPUT_TYPE = Attribute
    PASSED -> text_line (writer TEXTLINE_1)
text_line (writer TEXTLINE_1)
    attributes: text_line_data buffer

Bookmark: Reading LOD2 buildig model (previously converted from IFC)
multiHuset_LOD2_surfaces (reader XML_1)
    attributes: gml_parent_id xml_buffer, gml_parent_property xml_buffer, gml_id xml_buffer, gml_surfaceProperty xml_geometry, gml_multiSurfaceProperty xml_geometry
    -> Aggregator_Multihuset
Aggregator_Multihuset
    ACCUM_ATTRS_NAME = Use Attributes From One Feature
    AGGREGATE_TYPE = Homogeneous Collection (If Possible)
    MODE = Geometry - Assemble One Level
    ORDERED = No
    SEP = ,
    AGGREGATE -> GeometryExtractor_3
    AGGREGATE -> FeatureColorSetter
GeometryExtractor_3
    ATTR = _geometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> XMLTemplater_5 [OTHERBUILDINGS]
FeatureColorSetter
    COLOR = 0,0,0
    FILL_COLOR = 0.6, 0.6, 0.6
    MODE = Fixed
    COLORED -> FeatureColorSetter_Colored
FeatureColorSetter_Colored: Inspector

Bookmark: Reading city model (Sketchup)
  Data for this reader is not public.
AttributeExposer
    ATTR_LIST = _gml_id_BD,_BD_lowerCorner,_BD_upperCorner
    -> AttributeRenamer
AttributeRenamer
    ATTR_TABLE:
      RENAME_SET_DEFAULT _BD_lowerCorner > _lowerCorner
      RENAME_SET_DEFAULT _BD_upperCorner > _upperCorner
    -> StringReplacer
StringReplacer
    CASE = NO
    FIND_TEXT = SGP.BY.
    NO_MATCH = _FME_NO_OP_
    REGEXP = NO
    REPLACE_TEXT = id-
    SRC_ATTRS = _gml_id_BD
    -> GeometryExtractor_2
GeometryExtractor_2
    ATTR = _geometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> XMLTemplater_5 [OTHERBUILDINGS]
