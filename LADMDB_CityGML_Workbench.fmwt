FME workspace LADMDB_CityGML_Workbench.fmwt
Title: LADMDB_CityGML_Workbench

Parameters:
- SourceDataset_GML = $(FME_MF_DIR)BrygganCityModelCityGML3_Groups.gml   # Source Geography Markup Language (GML) File(s)
- SourceDataset_XML_6 = $(FME_MF_DIR)BrygganCityModelCityGML3_Groups.gml   # Source XML File(s)
- SourceDataset_GML_3 = $(FME_MF_DIR)BrygganCityModelCityGML3_Groups.gml   # Source Geography Markup Language (GML) File(s)
- SourceDataset_XML = $(FME_MF_DIR)LADM_instance.xml   # Source XML File(s)

Readers:
- GML_1: GML from $(SourceDataset_GML)
- XML_1: XML from $(SourceDataset_XML_6)
- GML_2: GML from $(SourceDataset_GML_3)
- XML_2: XML from $(SourceDataset_XML)

Note: Workspace for creating LADM database and integrating LADM with 3D city models (based on the CityGML3.0 standard). Created with FME 2017.0. / Since cadastral information is imported as separate feature types in FME, these single features have to be merged into a LADM database at first. According to the definition of LADM and the UML diagram of CityGML3.0, these two standards can be integrated by connecting common key fields. / A relevant master thesis can be found at: https://lup.lub.lu.se/student-papers/search/publication/8986918
Note: This workspace is released under the 3-Clause BSD License. For details, see https://opensource.org/licenses/BSD-3-Clause / This work was supported by the research platform, Smart Built Environment program under Grant 2016-01981 (financed by Formas, Vinnova and Swedish Energy Agency) and Lund University. / Copyright (c) 2019, Lunds universitet / All rights reserved.
TestFilter_Cadastre: Inspector
CityModel: Inspector
AttributeKeeper
    KEEP_ATTRS = dimension,area,suID,pID,volume,name,share,buID,type,label,rID,uID
    -> LADM_DB
    -> Integration [SUPPLIER]
    -> Integration_2 [SUPPLIER]
Integration_2: FeatureMerger
    ATTR_ACCUM_MODE = Merge Supplier
    ATTR_CONFLICT_RES = Use Requestor
    IGNORE_NULLS = No
    JOIN_KEYS = @Value(gml_id) @Value(name) AUTO
    MERGE_TYPE = Attributes and Geometry
    PROCESS_DUPS = NO
    REJECT_NULL_MISSING_KEYS = No
    SUPPLIERS_FIRST = No
    MERGED -> WithCityObjectMember
WithCityObjectMember: Inspector
LADM_DB: Inspector

Bookmark: Integration of Cadastral Data
LA_RRR (reader XML_2)
    attributes: pID xml_char(8), rID xml_decimal(3,0), share xml_char(4), type xml_char(10), xml_fragment xml_xml, xml_id xml_char(14), xml_matched_element xml_char(7), xml_parent_child_pos xml_char(1), xml_parent_id xml_char(1)
    -> FeatureMerger [REQUESTOR]
LA_Party (reader XML_2)
    attributes: pID xml_char(8), type xml_char(13), xml_fragment xml_xml, xml_id xml_char(16), xml_matched_element xml_char(9), xml_parent_child_pos xml_char(1), xml_parent_id xml_char(1)
    -> FeatureMerger [SUPPLIER]
FeatureMerger
    ATTR_ACCUM_MODE = Merge Supplier
    ATTR_CONFLICT_RES = Use Requestor
    CLEANING_TOLERANCE = None
    IGNORE_NULLS = No
    JOIN_KEYS = @Value(pID) @Value(pID) AUTO
    MERGE_TYPE = Attributes Only
    PROCESS_DUPS = NO
    REJECT_NULL_MISSING_KEYS = No
    SUPPLIERS_FIRST = No
    MERGED -> FeatureMerger_2 [SUPPLIER]
LA_BAUnit (reader XML_2)
    attributes: name xml_char(11), rID xml_decimal(3,0), uID xml_decimal(7,0), xml_fragment xml_xml, xml_id xml_char(17), xml_matched_element xml_char(10), xml_parent_child_pos xml_char(1), xml_parent_id xml_char(1)
    -> FeatureMerger_2 [REQUESTOR]
FeatureMerger_2
    ATTR_ACCUM_MODE = Merge Supplier
    ATTR_CONFLICT_RES = Use Requestor
    CLEANING_TOLERANCE = None
    IGNORE_NULLS = No
    JOIN_KEYS = @Value(rID) @Value(rID) AUTO
    MERGE_TYPE = Attributes Only
    PROCESS_DUPS = NO
    REJECT_NULL_MISSING_KEYS = No
    SUPPLIERS_FIRST = No
    MERGED -> FeatureMerger_3 [SUPPLIER]
LA_SpatialUnit (reader XML_2)
    attributes: area xml_char(8), dimension xml_char(3), label xml_decimal(9,0), name xml_char(10), suID xml_decimal(6,0), uID xml_decimal(7,0), xml_fragment xml_xml, xml_id xml_char(22), xml_matched_element xml_char(15), xml_parent_child_pos xml_char(1), xml_parent_id xml_char(1)
    -> FeatureMerger_3 [REQUESTOR]
FeatureMerger_3
    ATTR_ACCUM_MODE = Merge Supplier
    ATTR_CONFLICT_RES = Use Requestor
    CLEANING_TOLERANCE = None
    IGNORE_NULLS = No
    JOIN_KEYS = @Value(uID) @Value(uID) AUTO
    MERGE_TYPE = Attributes Only
    PROCESS_DUPS = NO
    REJECT_NULL_MISSING_KEYS = No
    SUPPLIERS_FIRST = No
    MERGED -> FeatureMerger_4 [SUPPLIER]
LA_LegalSpaceBuildingUnit (reader XML_2)
    attributes: area xml_char(11), buID xml_decimal(10,0), suID xml_decimal(6,0), type xml_char(11), volume xml_char(12), xml_fragment xml_xml, xml_id xml_char(33), xml_matched_element xml_char(26), xml_parent_child_pos xml_char(1), xml_parent_id xml_char(1)
    -> FeatureMerger_4 [REQUESTOR]
FeatureMerger_4
    ATTR_ACCUM_MODE = Merge Supplier
    ATTR_CONFLICT_RES = Use Requestor
    CLEANING_TOLERANCE = None
    IGNORE_NULLS = No
    JOIN_KEYS = @Value(suID) @Value(suID) AUTO
    MERGE_TYPE = Attributes Only
    PROCESS_DUPS = NO
    REJECT_NULL_MISSING_KEYS = No
    SUPPLIERS_FIRST = No
    MERGED -> AttributeKeeper

Bookmark: 3D city models with CityGML3 standard
  The format of Building and BuildingUnit is XML. For CityObjectGroup, it is GML.
  These readers must be connected to the output from the FME workbench brygganIFC_2_CityGML3_GitHUB.fmw included in the same GitHUB as this workbench.
Building (reader XML_1)
    attributes: Building.id xml_char(40), buildingSubdivision.BuildingUnit{}.class xml_char(10), buildingSubdivision.BuildingUnit{}.genericAttribute.StringAttribute{}.name xml_char(17), buildingSubdivision.BuildingUnit{}.genericAttribute.StringAttribute{}.value xml_char(10), buildingSubdivision.BuildingUnit{}.id xml_char(10), buildingSubdivision.BuildingUnit{}.lod1Solid.Solid.exterior.Shell.surfaceMember{}.Surface.id xml_char(44), buildingSubdivision.BuildingUnit{}.lod1Solid.Solid.exterior.Shell.surfaceMember{}.Surface.patches.PolygonPatch.exterior.LinearRing.posList xml_char(4841), buildingSubdivision.BuildingUnit{}.lod1Solid.Solid.exterior.Shell.surfaceMember{}.Surface.patches.PolygonPatch.interior.LinearRing.posList xml_char(1455), buildingSubdivision.BuildingUnit{}.lod1Solid.Solid.exterior.Shell.surfaceMember{}.Surface.patches.PolygonPatch.interior{}.LinearRing.posList xml_char(701), buildingSubdivision.BuildingUnit{}.lod1Solid.Solid.id xml_char(42), buildingSubdivision.BuildingUnit{}.lod1Solid.Solid.srsDimension xml_decimal(2,0), buildingSubdivision.BuildingUnit{}.lod1Solid.Solid.srsName xml_char(15), buildingSubdivision.BuildingUnit{}.schemaLocation xml_char(266), buildingSubdivision.BuildingUnit{}.spaceType xml_char(7), description xml_char(52), lod2MultiSurface.MultiSurface.id xml_char(42), lod2MultiSurface.MultiSurface.srsDimension xml_decimal(2,0), lod2MultiSurface.MultiSurface.srsName xml_char(10), lod2MultiSurface.MultiSurface.surfaceMember{}.Surface.id xml_char(44), lod2MultiSurface.MultiSurface.surfaceMember{}.Surface.patches.PolygonPatch.exterior.LinearRing.posList xml_char(2466), name xml_char(36), spaceType xml_char(9), xml_fragment xml_xml, xml_id xml_char(20), xml_matched_element xml_char(9), xml_parent_child_pos xml_char(1), xml_parent_id xml_char(1)
    -> Geometry_Building
Geometry_Building: GeometryReplacer
    KIND_LONG = GML
    REMOVE_ATTRIBUTE = Yes
    SOURCE = @Value(xml_fragment)
    SRS_AXIS_ORDER_DISPLAY = Automatic
    -> TestFilter
TestFilter
    DEFAULT_VALUE = Buildings
    TEST_LIST = "BOOL_OP,OR,COMPOSITE_TEST,""""""<Unused>"""""",TEST_CLAUSE,CASE_INSENSITIVE_TEST @Value(description) CONTAINS 3D",Cadastre
    Cadastre -> TestFilter_Cadastre
    Buildings -> FeatureColorSetter_buildings
FeatureColorSetter_buildings
    COLOR = 0.588235,0.588235,0.588235
    FILL_COLOR = 0.854902,0.854902,0.854902
    MODE = Fixed
    COLORED -> CityModel
BuildingUnit (reader XML_1)
    attributes: BuildingUnit.id xml_char(10), BuildingUnit.schemaLocation xml_char(266), class xml_char(10), genericAttribute.StringAttribute{}.name xml_char(17), genericAttribute.StringAttribute{}.value xml_char(10), lod1Solid.Solid.exterior.Shell.surfaceMember{}.Surface.id xml_char(44), lod1Solid.Solid.exterior.Shell.surfaceMember{}.Surface.patches.PolygonPatch.exterior.LinearRing.posList xml_char(4841), lod1Solid.Solid.exterior.Shell.surfaceMember{}.Surface.patches.PolygonPatch.interior.LinearRing.posList xml_char(1455), lod1Solid.Solid.exterior.Shell.surfaceMember{}.Surface.patches.PolygonPatch.interior{}.LinearRing.posList xml_char(701), lod1Solid.Solid.id xml_char(42), lod1Solid.Solid.srsDimension xml_decimal(2,0), lod1Solid.Solid.srsName xml_char(15), spaceType xml_char(7), xml_fragment xml_xml, xml_id xml_char(28), xml_matched_element xml_char(13), xml_parent_child_pos xml_decimal(4,0), xml_parent_id xml_char(18)
    -> GeometryReplace
GeometryReplace: GeometryReplacer
    KIND_LONG = GML
    REMOVE_ATTRIBUTE = Yes
    SOURCE = @Value(xml_fragment)
    SRS_AXIS_ORDER_DISPLAY = Automatic
    -> Integration [REQUESTOR]
    -> GeometryReplace_Output
GeometryReplace_Output: Inspector
CityObjectGroup (reader GML_2)
    attributes: creationDate xml_datetime, terminationDate xml_datetime, validFrom xml_datetime, validTo xml_datetime, relativeToTerrain xml_char(33), relativeToWater xml_char(38), externalReference{}.ExternalReference.targetResource xml_buffer, externalReference{}.ExternalReference.informationSystem xml_buffer, externalReference{}.ExternalReference.relationType xml_buffer, generalizesTo{}.nilReason xml_buffer, generalizesTo{}.gml_remoteSchema xml_buffer, generalizesTo{}.xlink_href xml_buffer, generalizesTo{}.owns xml_boolean, appearance{}.nilReason xml_buffer, appearance{}.gml_remoteSchema xml_buffer, appearance{}.xlink_href xml_buffer, appearance{}.owns xml_boolean, genericAttribute{}.DoubleAttribute.name xml_buffer, genericAttribute{}.DoubleAttribute.value xml_real64, genericAttribute{}.MeasureAttribute.name xml_buffer, genericAttribute{}.MeasureAttribute.value xml_real64, genericAttribute{}.MeasureAttribute.value.uom xml_buffer, genericAttribute{}.DateAttribute.name xml_buffer, genericAttribute{}.DateAttribute.value xml_date, genericAttribute{}.IntAttribute.name xml_buffer, genericAttribute{}.IntAttribute.value xml_int64, genericAttribute{}.GenericAttributeSet.name xml_buffer, genericAttribute{}.GenericAttributeSet.codeSpace xml_buffer, genericAttribute{}.GenericAttributeSet.genericAttribute{}.DoubleAttribute xml_xml, genericAttribute{}.GenericAttributeSet.genericAttribute{}.MeasureAttribute xml_xml,
      genericAttribute{}.GenericAttributeSet.genericAttribute{}.DateAttribute xml_xml, genericAttribute{}.GenericAttributeSet.genericAttribute{}.IntAttribute xml_xml, genericAttribute{}.GenericAttributeSet.genericAttribute{}.GenericAttributeSet xml_xml, genericAttribute{}.GenericAttributeSet.genericAttribute{}.StringAttribute xml_xml, genericAttribute{}.GenericAttributeSet.genericAttribute{}.UriAttribute xml_xml, genericAttribute{}.StringAttribute.name xml_buffer, genericAttribute{}.StringAttribute.value xml_buffer, genericAttribute{}.UriAttribute.name xml_buffer, genericAttribute{}.UriAttribute.value xml_buffer, dynamizer{}.nilReason xml_buffer, dynamizer{}.gml_remoteSchema xml_buffer, dynamizer{}.xlink_href xml_buffer, dynamizer{}.owns xml_boolean, class xml_buffer, class.codeSpace xml_buffer, function{} xml_buffer, function{}.codeSpace xml_buffer, usage{} xml_buffer, usage{}.codeSpace xml_buffer, groupMember{}.nilReason xml_buffer, groupMember{}.gml_remoteSchema xml_buffer, groupMember{}.xlink_href xml_buffer, groupMember{}.owns xml_boolean, groupMember{}.Role.gml_id xml_buffer, groupMember{}.Role.role xml_buffer, groupMember{}.Role.groupMember.nilReason xml_buffer, groupMember{}.Role.groupMember.gml_remoteSchema xml_buffer, groupMember{}.Role.groupMember.xlink_href xml_buffer, groupMember{}.Role.groupMember.owns xml_boolean, parent.nilReason xml_buffer,
      parent.gml_remoteSchema xml_buffer, parent.xlink_href xml_buffer, parent.owns xml_boolean, groupSpace.nilReason xml_buffer, groupSpace.gml_remoteSchema xml_buffer, groupSpace.xlink_href xml_buffer, groupSpace.owns xml_boolean
    -> StringReplacer
StringReplacer
    CASE = NO
    FIND_TEXT = grp_
    NO_MATCH = _FME_NO_OP_
    REGEXP = NO
    SRC_ATTRS = gml_id
    -> Integration_2 [REQUESTOR]

Bookmark: Legal spaces integrated with LADM
Integration: FeatureMerger
    ATTR_ACCUM_MODE = Merge Supplier
    ATTR_CONFLICT_RES = Use Requestor
    IGNORE_NULLS = No
    JOIN_KEYS = @Value(class) @Value(name) AUTO
    MERGE_TYPE = Attributes and Geometry
    PROCESS_DUPS = NO
    REJECT_NULL_MISSING_KEYS = No
    SUPPLIERS_FIRST = No
    MERGED -> AttributeKeeper_Integrated_CityGML3_LADM
AttributeKeeper_Integrated_CityGML3_LADM
    KEEP_ATTRS = rID,buID,type,BuildingUnit.id,volume,class,share,name,uID,suID,pID
    -> TestFilter_2
    -> AppearanceSetter_LegalSpacesCombined [GEOMETRY]
    -> AttributeKeeper_Integrated_CityGML3_LADM_Output
TestFilter_2
    DEFAULT_VALUE = <UNFILTERED>
    TEST_LIST = "BOOL_OP,OR,COMPOSITE_TEST,""""""<Unused>"""""",TEST_CLAUSE,CASE_INSENSITIVE_TEST @Value(class) LIKE Bryggan 2",Bryggan2,"BOOL_OP,OR,COMPOSITE_TEST,""""""<Unused>"""""",TEST_CLAUSE,CASE_INSENSITIVE_TEST @Value(class) LIKE Bryggan 1",Bryggan1
    Bryggan2 -> AppearanceSetter_Bryggan2 [GEOMETRY]
    Bryggan1 -> AppearanceSetter_Bryggan1 [GEOMETRY]
AppearanceSetter_Bryggan2
    AMBIENT_COLOR = 1,0.666667,0
    DEF_STORAGE = Create New Definitions
    DIFFUSE_COLOR = 1,0.666667,0
    EMISSIVE_COLOR = 1,0.666667,0
    GQUERY:
      for $geom in //geometry
      where $geom/count(parent::geometry) = 0
      return number($geom/@fme_id)
    SET_ON_SIDE = Front and Back Sides
    SPECULAR_COLOR = 1,0.666667,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> AppearanceSetter_Bryggan2_Output
AppearanceSetter_Bryggan2_Output: Inspector
AppearanceSetter_Bryggan1
    AMBIENT_COLOR = 0,0.666667,0
    DEF_STORAGE = Create New Definitions
    DIFFUSE_COLOR = 0,0.666667,0
    EMISSIVE_COLOR = 0,0.666667,0
    GQUERY:
      for $geom in //geometry
      where $geom/count(parent::geometry) = 0
      return number($geom/@fme_id)
    SET_ON_SIDE = Front and Back Sides
    SPECULAR_COLOR = 0,0.666667,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> AppearanceSetter_Bryggan1_Output
AppearanceSetter_Bryggan1_Output: Inspector
AppearanceSetter_LegalSpacesCombined
    AMBIENT_COLOR = 0.666667,0.333333,0
    DEF_STORAGE = Create New Definitions
    DIFFUSE_COLOR = 0.666667,0.333333,0
    EMISSIVE_COLOR = 0.666667,0.333333,0
    GQUERY:
      for $geom in //geometry
      where $geom/count(parent::geometry) = 0
      return number($geom/@fme_id)
    SET_ON_SIDE = Front and Back Sides
    SPECULAR_COLOR = 0.666667,0.333333,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> LegalSpacesCombined
LegalSpacesCombined: Inspector
AttributeKeeper_Integrated_CityGML3_LADM_Output: Inspector
